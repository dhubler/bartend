module bartend {
  namespace "";
  prefix "";
  revision 0;
  description "Bartender is an app that will mix a drink by turning on a set of 
    liquid pumps";

  list pump {
    description "direct access to hardware pumps";
    key "id";
    
    leaf id {
      description "ids from 0-8 for the installed pumps";
      type int32;
    }

    leaf gpioPin {
      description "Raspberry PI GPIO pin number. Do not change unless you're rewired your Pi.";
    	type int32;
    }

    leaf timeToVolumeRatioMs {
      description "number of millisecs to turn on pump to pour one milliliter";
      type int32;
    }

    leaf liquid {
      description "name of the liquid. If name does not match (case sensitive) recipe 
        ingredient exactly, it will not recognized as same liquid.";
      type string;
    }

    action on {
        description "turn on the pump";
    }

    action off {
        description "turn off the pump";
    }
  }

  list available {
    description "list of only the drinks that are available to make given the available ingredients at the pumps";
    config false;
    key "name";

    uses recipeDef;

    action make {
      description "make this drink";

    	input {
    		leaf multiplier {
    			description "Optional, make it a double by passing 2 or sample it by passing 
             0.1";
    			type decimal64;
    		}
    	}
    }
  }

  list recipe {
    description "list of all drinks known to this bartender";
    key "name";

    uses recipeDef;

    leaf madeCount {
      description "number of times the this recipe was made";
      type int32;
      config false;
    }
  }

  leaf-list liquids {
    description "all the unique liquids found across all recipes";
    config false;
    type string;
  }

  container drink {
    description "current drink recipe in progress";
    config false;

    notification update {
      description "status update for the drink in progress. Can be a firehose so use
        notification filters as defined in IETF protocols if you limit the amount";

      leaf name {
        description "recipe name";
        type string;
      }

      leaf percentComplete {
        description "0-100 percent complete with drink";
        type int32;
      }

      leaf complete {
        description "true if drink has finished being made";
        type boolean;
      }

      leaf aborted {
        description "was the drink stopped mid pour";
        type boolean;
      }

      list pour {

        description "ingredients from recipe that are available in the pumps and would
          be poured automatically";

        key "pumpId";

        leaf pumpId {
          description "unique id for this tap";
          type int32;
        }

        uses ingredient;

        leaf complete {
          description "is this liquid done pouring";
          type boolean;
        }

        leaf percentComplete {
          description "what percentage is this liquid complete pouring";
          type int32;
        }
      }
    }

    action stop {
      description "Stop making drink where ever in the process it is";
    } 
  }

  grouping recipeDef {

    leaf name {
      description "name of drink";
      type string;
    }

    leaf description {
      description "description of drink";
      type string;
    }

    list ingredient {
      description "ingredients for drink";
      key "liquid";
      uses ingredient;
    }
  }  
  
  grouping ingredient {

    leaf liquid {
      description "liquid name. If name does not match (case sensitive) pump 
        liquid exactly, it will not recognized as same liquid.";
      type string;
    }

    leaf amount {
      description "in ounces of liquid";
      type decimal64;
    }
  }
}
