module isaac {
  namespace "";
  prefix "";
  revision 0;

  list pumps {
    key "id";
    leaf id {
      type int32;
    }
    leaf timeToVolumeRatio {
      description "Number of millisecs to turn on pump to pour one unit (e.g. oz) of water";
      type decimal64;
      default "10";
    }
    leaf liquid {
      type string;
    }
  }

  leaf-list liquids {
    config "false";
    type string;
  }

  group drink {
    leaf name {
      type string;
    }
    list ingredient {
      leaf liquid {
        type string;
      }
      leaf amount {
        type decimal64;
      }
    }
  }

  list availableDrinks {
    key "name";
    uses drink;
    action make {
      input {}
    }
  }

  list recipe {
    key "name";
    uses drink;
  }

  action calibrateStart {
    input {
    }
  }

  action calibrateStop {
    input {
      leaf update {
        type boolean;
      }
    }
    output {
      leaf timeToVolumeRatio {
        type decimal64;
      }
    }
  }
}
